(defun drawlegs (pt1 legL legw /)
  (setq pt2 (polar pt1 0.0 legL))
  (setq pt3 (polar pt2 (/ pi 2.0) legw))
  (setq pt4 (polar pt3 pi legL))
  (command "pline" pt1 pt2 pt3 pt4 "C")
)

(defun tablelegs (/ L w pt thk L1 H oldsnap olsnap3d tvals)
  (setq oldsnap (getvar 'osmode))
  (setq oldsnap3d (getvar '3dosmode))
  (setvar 'osmode 0)
  (setvar '3dosmode 1)
  (if (not AH:getvalsm) (load "Multi Getvals"))
  (setq tvals (AH:getvalsm (list "Enter table size" "Enter length" 5 4 "1200" "Enter width" 5 4 "900" "Table thickness" 5 4 "30" "Enter height" 5 4 "900" "Enter Leg size" 5 4 "100")))
  (setq L (atof (nth 0 tvals))
        w (atof (nth 1 tvals))
        thk (atof (nth 2 tvals))
        H (atof (nth 3 tvals))
        L1 (atof (nth 4 tvals))
  )
  (setq pt (getpoint "Pick start point"))
  (command "-vpoint" "1,1,1")
  (drawlegs pt L w)
  (command "extrude" "last" "" thk)
  (command "move" "L" "" (list 0.0 0.0 0.0) (list 0.0 0.0 H))
  (drawlegs pt L1 L1)
  (command "extrude" "last" "" H)
  (setq pt (polar pt 0.0 (- l L1)))
  (drawlegs pt L1 L1)
  (command "extrude" "last" "" H)
  (setq pt (polar pt (* pi 0.5) (- w L1)))
  (drawlegs pt L1 L1)
  (command "extrude" "last" "" H)
  (setq pt (polar pt pi (- l L1)))
  (drawlegs pt L1 L1)
  (command "extrude" "last" "" H)
  (command "zoom" "e")
  (setvar 'osmode oldsnap)
  (setvar '3dosmode oldsnap3d)
  (alert " _Vpoint 1,1,1 \nJust for viewing remove the \n viewpoint from code\nto stay in plan view")
  (princ)
)

(tablelegs)
