(defun c:incoord (/ pc)
  (while (setq pc (getpoint "\nClick on the point or Enter to End : "))
    ;(command ".text" pc "" "" (strcat "Z = " (rtos (caddr pc))))
    (command ".text" pc "" "" (strcat "X = " (rtos (car pc)) ",Y = " (rtos (cadr pc)) ",Z = " (rtos (caddr pc))))
  )
  (princ)
)
(princ "\nType incoord to start")
(princ)
